; AutoCAD MCP - placeholder LISP script (Phase 0 scaffold).
; Real scripts will be added in later phases for legacy operations that have no .NET API.
(defun c:acadmcp-ping () (princ "\nAcadMcp LISP loader OK") (princ))
